Attribute VB_Name = "IG"

Public Sub Alahuz()

  Dim ss As AcadSelectionSet
  Dim obj As AcadObject
  Dim txt As AcadText
  Dim str As String
  
  On Error Resume Next
  ThisDrawing.SelectionSets("FZALAHUZ").Delete
  Set ss = ThisDrawing.SelectionSets.Add("FZALAHUZ")
  ThisDrawing.Utility.Prompt "Válassz aláhúzandó feliratokat" & vbCrLf
  ss.SelectOnScreen
  
  For Each obj In ss
    
    If TypeOf obj Is AcadText Then
      
      Set txt = obj
      
      str = txt.TextString
      
      
      If UCase(Left(str, 3)) <> "%%U" Then
      
        txt.TextString = "%%u" + txt.TextString
        txt.Update
        
      End If
    
    End If
    
  
  Next


End Sub

Public Sub Alahuz_ki()

  Dim ss As AcadSelectionSet
  Dim obj As AcadObject
  Dim txt As AcadText
  Dim str As String
  
  On Error Resume Next
  ThisDrawing.SelectionSets("FZALAHUZ").Delete
  Set ss = ThisDrawing.SelectionSets.Add("FZALAHUZ")
  ThisDrawing.Utility.Prompt "Aláhúzás ki: " & vbCrLf
  ss.SelectOnScreen
  
  For Each obj In ss
    
    If TypeOf obj Is AcadText Then
      
      Set txt = obj
      
      str = txt.TextString
      
      
      If UCase(Left(str, 3)) = "%%U" Then
      
        txt.TextString = Right(str, Len(str) - 3)
        txt.Update
        
      End If
    
    End If
      
  Next

End Sub

Attribute VB_Name = "frmAlahuz"
Attribute VB_Base = "0{1B6FDC31-F252-4619-8F6A-9B14B7C87365}{E3A6CBF2-F858-4EE3-B38C-D21915053A0F}"
Attribute VB_GlobalNameSpace = False
Attribute VB_Creatable = False
Attribute VB_PredeclaredId = True
Attribute VB_Exposed = False
Attribute VB_TemplateDerived = False
Attribute VB_Customizable = False

Private Sub CommandButton1_Click()
  IG.Alahuz
End Sub

Private Sub CommandButton2_Click()
  IG.Alahuz_ki
End Sub
